(defun c:9test2()
  (sub_chk_layer)
  (sub_chk_style)
  (prin1)
  )
(defun sub_chk_layer()
  (setq check_lytemp(tblsearch "layer" "str"))
  (if (= check_lytemp nil)
    (command "layer" "n" "str" "c" 1 "str" "")
    )
  (setq check_lytemp(tblsearch "layer" "txt"))
  (if (= check_lytemp nil)
    (command "layer" "n" "txt" "c" 3 "txt" "")
    )
  (setq check_lytemp(tblsearch "layer" "dim"))
  (if (= check_lytemp nil)
    (command "layer" "n" "dim" "c" 5 "dim" "")
    )
  (setq check_lytemp(tblsearch "layer" "hat"))
  (if (= check_lytemp nil)
    (command "layer" "n" "hat" "c" 6 "hat" "")
    )
  (setq check_lytemp(tblsearch "layer" "cen"))
  (if (= check_lytemp nil)
    (command "layer" "n" "cen" "c" 2 "cen" "")
    )
  (setq check_lytemp(tblsearch "layer" "hid"))
  (if (= check_lytemp nil)
    (command "layer" "n" "hid" "c" 2 "hid" "")
    )
  )
(defun sub_chk_style()
  (setq check_sytemp(tblsearch "style" "china"))
  (if (= check_sytemp nil)
    (command "style" "china" "txt,chineset" "" "" "" "" "" "")
    )
  (setq check_sytemp(tblsearch "style" "kk"))
  (if (= check_sytemp nil)
    (command "style" "kk" "标楷体" "" "" "" "" "")
    (prompt "KK OK!")
    )
  (prompt "\n OK!")
  )
