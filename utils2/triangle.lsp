(defun c:triangle()
       	(setq pa (getpoint "input left-down point:"))
	(setq A (getreal "input base length:"))
  	(setq B (getreal "input oblique side length:"))
  	(setq C (getreal "input oblique side length:"))
  	(setq temp (+ A B C))
  	(setq S (/ temp 2))
  ;;;	(setq area_tri (* S ( - (S A)( - (S B))( - (S C)))))
  	(setq tempsa (- S A ))
  	(setq tempsb (- S B ))
  	(setq tempsc (- s c ))
  	(setq area_tri (sqrt( * S tempsa tempsb tempsc)))
  ;;;	(setq H (/ * (area_tri 2 A)))
  	(setq temp1 ( * area_tri 2))
  	(setq H (/ temp1 A))
  	(setq left_length (sqrt (/ (expt c 2)(expt H 2))))
  	(setq pb (polar pa 0 A))
  	(setq point (polar pa 0 left_length))
  	(setq high_point (polar point (/ pi 2) H))
  	(command "pline" pa high_point "")
  	(command "pline" pb high_point "")
  	(command "pline" point high_point "")
  	(command "pline" pa pb "")
  	(prin1)
  )
