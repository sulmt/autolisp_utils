(defun c:lsp_47()
  (setvar "cmdecho" 0)
  (setq ffn (getfiled "选择文件" "" "txt" 2))
  (setq pt (getpoint "\n set start_point"))
  (setq pd (getdist "\n high"))
  (setq ff (open ffn "r"))
  (setq data (read-line ff))
  (command "text" pt pd 0 data)
  (setq data (read-line ff))
  (while data
    (command "text" "" data)
    (setq data (read-line ff))
    )
  (close ff)
  (prin1)
  )
