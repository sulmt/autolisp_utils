(defun c:cal_num()
  (setq ss (ssget))
  (setq n 0);;; count
  (setq n_line 0 n_cir 0 n_arc 0)
  (repeat (sslength ss)
    (setq en (ssname ss n))
    (setq endata (entget en))
    (setq entype (cdr (assoc 0 endata)))
    (cond ((if (= entype "LWPOLYLINE") (setq n_line (+ n_line 1))))
	  ((if (= entype "CIRCLE") (setq n_cir (+ n_cir 1))))
	  ((if (= entype "ARC") (setq n_arc (+ n_arc 1))))
	  )
    (setq n (+ n 1))
    )
  (sub_write_data)
  (prin1)
  )

(defun sub_write_data()
  (setq dat_file (getfiled "write pra" "E:\autolisp\test.txt" "txt" 2))
  (setq ff (open dat_file "w"))
  (write-line "对象类别 数量" ff)
  (write-line (strcat "LINE " (itoa n_line)) ff)
  (write-line (strcat "CIRCLE " (itoa n_cir)) ff)
  (write-line (strcat "ARC " (itoa n_arc)) ff)
  (close ff)
  )
(prompt "*****************<<C:10test3 to conclulate number>>****************")
(prin1)
