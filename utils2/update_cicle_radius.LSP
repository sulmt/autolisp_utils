;;;change radius for chosen circle
(defun c:test1()
  (setq new_rad (getreal "please input new radius:"))
  (prompt "\n <<FRAME SELECTION>>")
  (setq ss(ssget))
  (setq n 0)
  (setq k 0)
  (repeat (sslength ss)
    (setq en (ssname ss n))
    (setq endata (entget en))
    (setq entype (cdr (assoc 0 endata)))
    (if (= entype "CIRCLE")
      (sub_upd_rad)
      )
    (setq n (+ 1 n))
    )
  (prompt "********锅娘炮感谢你的使用**************\n")
  (prompt "********锅娘炮说你很帅**************")
  (prompt "********锅娘炮说你比他还帅**************")
  (prompt "********锅娘炮说他是土豪**************")
  (prompt "********锅娘炮说谁比他黑**************")
  (prompt "********锅娘炮!王炸!**************")

 ;;; (princ (strcat "\n totally<" (itoa k) "> updated radius = "rtos new_rad))
  (prin1)
  )


(defun sub_upd_rad()
  (setq old_rad_list(assoc 40 endata))
  (setq new_rad_list(cons 40 new_rad))
  (setq endata(subst new_rad_list old_rad_list endata))
  (entmod endata)
  (setq k (+ 1 k))
  )
(prompt "*****************<<C:test1 to update circle radius>>****************")
(prin1)
