(defun c:g_p()
  (setq size (getstring "please input graph size A0,A1,,,A4:"))
  (if (= size "")
    (setq size "A3")
    )
  (setq size (strcase size));;;a->A
;;;  (cond (= size "A0") (setq p2 '(1189,841))
;;;  	(= size "A1") (setq p2 '(841,594))
;;;  	(= size "A2") (setq p2 '(594,420))
;;;  	(= size "A3") (setq p2 '(420,297))
;;;  	(= size "A4") (setq p2 '(297,210))
;;;	(t	(setq p2 '(420,297))
;;;	)
  (if (= size "A0") (setq p2 '(1189,841)))
  (if (= size "A1") (setq p2 '(841,594)))
  (if (= size "A2") (setq p2 '(594,420)))
  (if (= size "A3") (setq p2 '(420,297)))
  (if (= size "A4") (setq p2 '(297,210)))
  ;;;draw
  (setq p1 '(0,0))
  (command "rectang" p1 p2)
  (command "zoom" "A")
  (prin1)
  )
(prompt "*****************<<C:g_p to draw AX>>********************")
(prin1)
